import FreeCAD as App
import Part
import Draft
from FreeCAD import Base

# Crea un nuovo documento se non è già aperto
doc = App.ActiveDocument
if doc is None:
    doc = App.newDocument("CNC_MDF")

# Parametri del tavolo MDF
length = 500
width = 500
thickness = 6

# Creazione blocco MDF
mdf_block = Part.makeBox(length, width, thickness)

# Foro passante da 1mm al centro
hole_radius = 0.5
center_x = length / 2
center_y = width / 2
hole = Part.makeCylinder(hole_radius, thickness, Base.Vector(center_x, center_y, 0), Base.Vector(0, 0, 1))
final_shape = mdf_block.cut(hole)

# === Parametri scacchiera ===
square_size = 55  # mm (5.5 cm)
rows = 8
cols = 8
z_level = thickness + 0.1  # appena sopra il piano MDF
circle_radius = 3  # raggio 3mm = diametro 6mm

# Parametri per i fori LDR (rimangono invariati)
main_hole_radius = 2.5  # raggio 2.5mm = diametro 5mm per il foro principale
main_hole_depth = 3     # profondità del foro principale in mm
pin_hole_radius = 0.5   # raggio 0.5mm = diametro 1mm per i fori dei piedini
# Calcola la distanza per posizionare i fori dei piedini dentro l'alloggio principale
# Il bordo esterno del foro del piedino deve coincidere con il bordo dell'alloggio
# Distanza = raggio_alloggio - raggio_piedino
pin_distance = main_hole_radius - pin_hole_radius  # 2.5 - 0.5 = 2.0 mm
pin_depth = thickness   # i fori dei piedini saranno passanti

# Parametri per la griglia di scanalature cavi
groove_width = 1      # larghezza scanalature in mm
groove_depth = 1      # profondità scanalature in mm
offset_distance = 20  # distanza in mm per le linee parallele (2cm)

# Calcola il centro della tavola per posizionare la scacchiera
origin_x = (length - (cols * square_size)) / 2
origin_y = (width - (rows * square_size)) / 2

# Gruppo per la scacchiera
chessboard_group = doc.addObject("App::DocumentObjectGroup", "Scacchiera")

# Array per memorizzare i centri dei fori LDR
ldr_positions = []

# Crea i quadrati della scacchiera e i fori per gli LDR
for row in range(rows):
    for col in range(cols):
        # Calcola la posizione del quadrato
        x = origin_x + col * square_size
        y = origin_y + row * square_size

        # Crea il quadrato
        points = [
            Base.Vector(x, y, z_level),
            Base.Vector(x + square_size, y, z_level),
            Base.Vector(x + square_size, y + square_size, z_level),
            Base.Vector(x, y + square_size, z_level),
            Base.Vector(x, y, z_level)
        ]
        square_wire = Part.makePolygon(points)
        square_obj = doc.addObject("Part::Feature", f"Casella_{row}_{col}")
        square_obj.Shape = square_wire
        chessboard_group.addObject(square_obj)

        # Calcola il centro della casella
        cx = x + square_size / 2
        cy = y + square_size / 2

        # Salva la posizione del centro per le connessioni a griglia
        ldr_positions.append((cx, cy))

        # Crea il cerchietto centrale (diametro 6mm) come guida visiva
        circle_edge = Part.makeCircle(circle_radius, Base.Vector(cx, cy, z_level))
        circle_obj = doc.addObject("Part::Feature", f"Cerchio_{row}_{col}")
        circle_obj.Shape = circle_edge
        chessboard_group.addObject(circle_obj)

        # Crea il foro fresato principale al centro (5mm diametro, 3mm profondità)
        # FRESATO DALL'ALTO - l'LDR si inserisce da sopra
        main_hole = Part.makeCylinder(
            main_hole_radius,
            main_hole_depth,
            Base.Vector(cx, cy, thickness - main_hole_depth),  # Inizia da 3mm sotto la superficie superiore
            Base.Vector(0, 0, 1)
        )
        final_shape = final_shape.cut(main_hole)

        # Crea i due fori per i piedini dell'LDR (1mm diametro, passanti)
        # I terminali dell'LDR escono dal lato inferiore
        # Foro a nord
        north_pin_hole = Part.makeCylinder(
            pin_hole_radius,
            pin_depth,
            Base.Vector(cx, cy + pin_distance, 0),  # Parte dal fondo (z=0)
            Base.Vector(0, 0, 1)
        )
        final_shape = final_shape.cut(north_pin_hole)

        # Foro a sud
        south_pin_hole = Part.makeCylinder(
            pin_hole_radius,
            pin_depth,
            Base.Vector(cx, cy - pin_distance, 0),  # Parte dal fondo (z=0)
            Base.Vector(0, 0, 1)
        )
        final_shape = final_shape.cut(south_pin_hole)

# === NUOVA GRIGLIA DI SCANALATURE ===

# Calcola i limiti della griglia
grid_start_x = origin_x
grid_end_x = origin_x + cols * square_size
grid_start_y = origin_y
grid_end_y = origin_y + rows * square_size

# Margine per il perimetro esterno
perimeter_margin = 10  # mm dal bordo della scacchiera

# Limiti del perimetro
perim_start_x = grid_start_x - perimeter_margin
perim_end_x = grid_end_x + perimeter_margin
perim_start_y = grid_start_y - perimeter_margin
perim_end_y = grid_end_y + perimeter_margin

# 1. LINEE VERTICALI - Passano sui centri dei fori (colonne)
for col in range(cols):
    x_pos = origin_x + col * square_size + square_size/2

    # Linea principale sui centri
    main_vert_groove = Part.makeBox(
        groove_width,
        perim_end_y - perim_start_y,  # Estesa fino al perimetro
        groove_depth,
        Base.Vector(
            x_pos - groove_width/2,
            perim_start_y,
            0
        )
    )
    final_shape = final_shape.cut(main_vert_groove)

    # Linea parallela a +2cm (destra)
    if x_pos + offset_distance < perim_end_x:
        right_vert_groove = Part.makeBox(
            groove_width,
            perim_end_y - perim_start_y,
            groove_depth,
            Base.Vector(
                x_pos + offset_distance - groove_width/2,
                perim_start_y,
                0
            )
        )
        final_shape = final_shape.cut(right_vert_groove)

    # Linea parallela a -2cm (sinistra)
    if x_pos - offset_distance > perim_start_x:
        left_vert_groove = Part.makeBox(
            groove_width,
            perim_end_y - perim_start_y,
            groove_depth,
            Base.Vector(
                x_pos - offset_distance - groove_width/2,
                perim_start_y,
                0
            )
        )
        final_shape = final_shape.cut(left_vert_groove)

# 2. LINEE ORIZZONTALI - Passano sui centri dei fori (righe)
for row in range(rows):
    y_pos = origin_y + row * square_size + square_size/2

    # Linea principale sui centri
    main_horiz_groove = Part.makeBox(
        perim_end_x - perim_start_x,  # Estesa fino al perimetro
        groove_width,
        groove_depth,
        Base.Vector(
            perim_start_x,
            y_pos - groove_width/2,
            0
        )
    )
    final_shape = final_shape.cut(main_horiz_groove)

    # Linea parallela a +2cm (sopra)
    if y_pos + offset_distance < perim_end_y:
        top_horiz_groove = Part.makeBox(
            perim_end_x - perim_start_x,
            groove_width,
            groove_depth,
            Base.Vector(
                perim_start_x,
                y_pos + offset_distance - groove_width/2,
                0
            )
        )
        final_shape = final_shape.cut(top_horiz_groove)

    # Linea parallela a -2cm (sotto)
    if y_pos - offset_distance > perim_start_y:
        bottom_horiz_groove = Part.makeBox(
            perim_end_x - perim_start_x,
            groove_width,
            groove_depth,
            Base.Vector(
                perim_start_x,
                y_pos - offset_distance - groove_width/2,
                0
            )
        )
        final_shape = final_shape.cut(bottom_horiz_groove)

# 3. PERIMETRO DI RACCORDO
# Lato sinistro
left_perim_groove = Part.makeBox(
    groove_width,
    perim_end_y - perim_start_y,
    groove_depth,
    Base.Vector(
        perim_start_x - groove_width/2,
        perim_start_y,
        0
    )
)
final_shape = final_shape.cut(left_perim_groove)

# Lato destro
right_perim_groove = Part.makeBox(
    groove_width,
    perim_end_y - perim_start_y,
    groove_depth,
    Base.Vector(
        perim_end_x - groove_width/2,
        perim_start_y,
        0
    )
)
final_shape = final_shape.cut(right_perim_groove)

# Lato inferiore
bottom_perim_groove = Part.makeBox(
    perim_end_x - perim_start_x,
    groove_width,
    groove_depth,
    Base.Vector(
        perim_start_x,
        perim_start_y - groove_width/2,
        0
    )
)
final_shape = final_shape.cut(bottom_perim_groove)

# Lato superiore
top_perim_groove = Part.makeBox(
    perim_end_x - perim_start_x,
    groove_width,
    groove_depth,
    Base.Vector(
        perim_start_x,
        perim_end_y - groove_width/2,
        0
    )
)
final_shape = final_shape.cut(top_perim_groove)

# Crea il rettangolo di contorno a 1mm di distanza (per visualizzazione)
frame_margin = 1  # mm
frame_thickness = 1  # mm

# Calcola le dimensioni del bordo esterno
inner_x = origin_x - frame_margin
inner_y = origin_y - frame_margin
inner_width = cols * square_size + 2 * frame_margin
inner_height = rows * square_size + 2 * frame_margin

# Crea il rettangolo esterno
outer_points = [
    Base.Vector(inner_x - frame_thickness, inner_y - frame_thickness, z_level),
    Base.Vector(inner_x + inner_width + frame_thickness, inner_y - frame_thickness, z_level),
    Base.Vector(inner_x + inner_width + frame_thickness, inner_y + inner_height + frame_thickness, z_level),
    Base.Vector(inner_x - frame_thickness, inner_y + inner_height + frame_thickness, z_level),
    Base.Vector(inner_x - frame_thickness, inner_y - frame_thickness, z_level)
]
outer_wire = Part.makePolygon(outer_points)

# Crea il rettangolo interno
inner_points = [
    Base.Vector(inner_x, inner_y, z_level),
    Base.Vector(inner_x + inner_width, inner_y, z_level),
    Base.Vector(inner_x + inner_width, inner_y + inner_height, z_level),
    Base.Vector(inner_x, inner_y + inner_height, z_level),
    Base.Vector(inner_x, inner_y, z_level)
]
inner_wire = Part.makePolygon(inner_points)

# Crea gli oggetti per i bordi
outer_obj = doc.addObject("Part::Feature", "Bordo_Esterno")
outer_obj.Shape = outer_wire
chessboard_group.addObject(outer_obj)

inner_obj = doc.addObject("Part::Feature", "Bordo_Interno")
inner_obj.Shape = inner_wire
chessboard_group.addObject(inner_obj)

# Aggiungi al documento l'oggetto MDF finale con tutti i fori
obj = doc.addObject("Part::Feature", "MDF_Model")
obj.Shape = final_shape

# Ricalcola il documento
doc.recompute()

# Seleziona la vista assometrica
if App.GuiUp:
    import FreeCADGui
    FreeCADGui.ActiveDocument.ActiveView.viewIsometric()
    FreeCADGui.SendMsgToActiveView("ViewFit")
